# eVTOL_requirements

## REQ-01: Position error must stay below 0.01 (Functional)
With matched initial states and no disturbances, sqrt((x-x_desired)^2+(y-y_desired)^2) must be strictly less than 0.01 at every logged simulation time. Check both point-to-point motion and one complete circle. Change PositionErrorLimit in Attributes to change the test threshold. Quantities are dimensionless.
